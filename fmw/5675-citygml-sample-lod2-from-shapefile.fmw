FME workspace 5675-citygml-sample-lod2-from-shapefile.fmw

Parameters:
- DestDataset_CITYGML = $(FME_MF_DIR)5677-single-building\single_building_gml_out.gml   # Destination CityGML Document
- GEOM = lod2MultiSurface   # CityGML Lod Name
- ROLE = cityObjectMember   # Feature Role
- DestDataset_CITYGML_3 = $(FME_MF_DIR)5677-single-building\single_building_gml_out.gml   # Destination CityGML Document
- SourceDataset_ESRISHAPE_11 = $(FME_MF_DIR)DHQG (1)\DHQG.shp   # Source Esri Shapefile(s)
- SourceDataset_ESRISHAPE_10 = $(FME_MF_DIR)DHQG (1)\roofEdge_Project.shp   # Source Esri Shapefile(s)
- SourceDataset_ESRISHAPE_15 = $(FME_MF_DIR)DHQG (1)\roofEdge_arch_Project.shp   # Source Esri Shapefile(s)
- SourceDataset_ESRISHAPE_17 = $(FME_MF_DIR)DHQG (1)\roofEdge.shp   # Source Esri Shapefile(s)
- SourceDataset_ESRISHAPE_12 = $(FME_MF_DIR)DHQG (1)\roofEdge_arch.shp   # Source Esri Shapefile(s)
- SourceDataset_ESRISHAPE = $(FME_MF_DIR)DHQG (1)\DHQG_Project.shp   # Source Esri Shapefile(s)
- SourceDataset_ESRISHAPE_13 = $(FME_MF_DIR)DHQG (1)\DHQG_48N.shp   # Source Esri Shapefile(s)
- SourceDataset_ESRISHAPE_14 = $(FME_MF_DIR)DHQG (1)\roofEdge_48N.shp   # Source Esri Shapefile(s)
- SourceDataset_ESRISHAPE_16 = $(FME_MF_DIR)DHQG (1)\roofEdge_arch_48N.shp   # Source Esri Shapefile(s)

Readers:
- ESRISHAPE_4: ESRISHAPE from $(SourceDataset_ESRISHAPE_11)
- ESRISHAPE_2: ESRISHAPE from $(SourceDataset_ESRISHAPE_10)
- ESRISHAPE_3: ESRISHAPE from $(SourceDataset_ESRISHAPE_15)
- ESRISHAPE_6: ESRISHAPE from $(SourceDataset_ESRISHAPE_17)
- ESRISHAPE_7: ESRISHAPE from $(SourceDataset_ESRISHAPE_12)
- ESRISHAPE_1: ESRISHAPE from $(SourceDataset_ESRISHAPE)
- ESRISHAPE_5: ESRISHAPE from $(SourceDataset_ESRISHAPE_13)
- ESRISHAPE_8: ESRISHAPE from $(SourceDataset_ESRISHAPE_14)
- ESRISHAPE_9: ESRISHAPE from $(SourceDataset_ESRISHAPE_16)

Writers:
- CITYGML_1: CITYGML to $(DestDataset_CITYGML)
- CITYGML_2: CITYGML to $(DestDataset_CITYGML_3) in LL-WGS84

DHQG_48N (reader ESRISHAPE_5)
    attributes: OBJECTID long, height short, name char(16), roof_heigh short, roof_type char(20), id long, base_h long, g_touching char(50), type char(15), Shape_Leng double, Shape_Area double
    -> UUIDGenerator_2
UUIDGenerator_2
    UUID_ATTR = _uuid
    -> AttributeFilter_3
AttributeFilter_3
    ATTR_VALUES = <EMPTY>,<MISSING>,<NULL>,<UNFILTERED>,road,building
    ATTR_NAME = type
    road -> Orientor_4
    building -> AttributeFilter
    building -> AttributeCreator_2
    building -> 3DForcer_2
    building -> Chopper
Orientor_4
    FLIP_APPEARANCES_CHOICE = Yes
    KIND = REVERSE
    ORIENTED -> AttributeCreator_6
AttributeCreator_6
    ATTR_TABLE:
      SET_TO citygml_lod_name = lod2MultiSurface
      SET_TO gml_id = @Value(_uuid)
    -> GeometryPropertySetter_5
GeometryPropertySetter_5
    SETTYPE_PARAM = Traits From Attributes
    REMOVE_ATTRIBUTE = No
    OVERWRITE_CHOICE = Yes
    SRC_ATTRS = citygml_lod_name
    SET -> Road (writer CITYGML_1)
Road (writer CITYGML_1)
AttributeCreator_2
    ATTR_TABLE:
      SET_TO gml_id = @Value(_uuid)
      SET_TO citygml_lod_name = lod2Solid
    -> Building (writer CITYGML_1)
Building (writer CITYGML_1)
AttributeFilter
    ATTR_VALUES = <EMPTY>,<MISSING>,<NULL>,<UNFILTERED>,hip,flat,mansard,arch
    ATTR_NAME = roof_type
    hip -> Junction_14
    hip -> Junction_16
    flat -> Junction_22
    mansard -> Junction_18
    mansard -> Junction_20
    arch -> Junction_12
Note: GeometryCoercer : Input
Junction_14
    -> Junction_15
Note: CenterLineReplacer : Input
Junction_16
    -> Junction_17
Note: AttributeCreator : Input
Junction_22
    -> Junction_23
Note: AttributeFilter : flat
Junction_23
    -> AttributeCreator
Note: 3DForcer_9 : Input
Junction_18
    -> Junction_19
Note: AttributeCreator : Input
Junction_20
    -> Junction_21
Note: AttributeFilter : mansard
Junction_21
    -> AttributeCreator
Note: 3DForcer_11 : Input
Junction_12
    -> Junction_13
DHQG_Project (reader ESRISHAPE_1)
    attributes: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
roofEdge_48N (reader ESRISHAPE_8)
    attributes: OBJECTID long, name char(50), roof_h short, roof_t char(20), wall_h short, id long, Shape_Leng double, Shape_Area double
    -> AttributeCreator
AttributeCreator
    ATTR_TABLE = SET_TO id = @Value(_uuid)
    -> AttributeFilter_2
AttributeFilter_2
    ATTR_VALUES = <EMPTY>,<MISSING>,<NULL>,<UNFILTERED>,flat,mansard,flat-hip
    ATTR_NAME = roof_t
    flat -> Junction_24
    flat -> Junction_26
    mansard -> Junction_32
    flat-hip -> Junction_28
    flat-hip -> Junction_30
Note: 3DForcer_5 : Input
Junction_24
    -> Junction_25
Note: 3DForcer_6 : Input
Junction_26
    -> Junction_27
Note: GeometryCoercer_2 : Input
Junction_28
    -> Junction_29
Note: CenterLineReplacer_2 : Input
Junction_30
    -> Junction_31
Note: 3DForcer_7 : Input
Junction_32
    -> Junction_33
roofEdge_Project (reader ESRISHAPE_2)
    attributes: OBJECTID long, name char(50), roof_h short, roof_t char(20), wall_h short, id long, Shape_Leng double, Shape_Area double
roofEdge (reader ESRISHAPE_6)
    attributes: name char(50), roof_h short, roof_t char(20), wall_h short, id long
RoofSurface00 (writer CITYGML_1)
    attributes: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

Bookmark: Wall-Floor Surface
3DForcer_2
    ZVALATTR = 0
    KEEPZVAL = No
    -> Orientor_2
Orientor_2
    FLIP_APPEARANCES_CHOICE = Yes
    KIND = REVERSE
    ORIENTED -> UUIDGenerator_4
UUIDGenerator_4
    UUID_ATTR = _uuid_ground
    -> AttributeCreator_4
AttributeCreator_4
    ATTR_TABLE:
      SET_TO citygml_lod_name = lod2MultiSurface
      SET_TO citygml_feature_role = boundedBy
      SET_TO gml_parent_id = @Value(_uuid)
      SET_TO gml_id = @Value(_uuid_ground)
    -> GeometryPropertySetter_3
GeometryPropertySetter_3
    SETTYPE_PARAM = Traits From Attributes
    REMOVE_ATTRIBUTE = No
    OVERWRITE_CHOICE = Yes
    SRC_ATTRS = citygml_feature_role citygml_lod_name gml_parent_id
    SET -> GroundSurface (writer CITYGML_1)
GroundSurface (writer CITYGML_1)
    attributes: citygml_feature_role xml_char(200)
Chopper
    REMNANT_ATTR = _remnant
    MAX_VERTICES = 2
    MODE = By Vertex
    CHOPPED_ATTR = _chopped
    -> Extruder_6
Extruder_6
    DISTANCE = @Value(height)
    DIRECTION = Vertical
    -> Orientor_3
Orientor_3
    FLIP_APPEARANCES_CHOICE = Yes
    KIND = REVERSE
    ORIENTED -> UUIDGenerator_3
UUIDGenerator_3
    UUID_ATTR = _uuid_wall
    -> AttributeCreator_5
AttributeCreator_5
    ATTR_TABLE:
      SET_TO citygml_lod_name = lod2MultiSurface
      SET_TO citygml_feature_role = boundedBy
      SET_TO gml_parent_id = @Value(_uuid)
      SET_TO gml_id = @Value(_uuid_wall)
    -> GeometryPropertySetter_4
GeometryPropertySetter_4
    SETTYPE_PARAM = Traits From Attributes
    REMOVE_ATTRIBUTE = No
    OVERWRITE_CHOICE = Yes
    SRC_ATTRS = citygml_lod_name
    SET -> WallSurface (writer CITYGML_1)
WallSurface (writer CITYGML_1)
    attributes: citygml_feature_role xml_char(200)

Bookmark: Hipped Roof
Note: AttributeFilter : hip
Junction_15
    -> GeometryCoercer
GeometryCoercer
    KIND = fme_line
    GQUERY:
      for $geom in //geometry
      where $geom/count(parent::geometry) = 0
      return number($geom/@fme_id)
    COERCED -> 3DForcer_4
3DForcer_4
    ZVALATTR = @Value(height)
    KEEPZVAL = No
    -> TINGenerator [POINTS/LINES]
Note: AttributeFilter : hip
Junction_17
    -> CenterLineReplacer
CenterLineReplacer
    MODE = Medial Axis
    CENTERLINE -> 3DForcer_3
3DForcer_3
    ZVALATTR = @Value(roof_heigh)
    KEEPZVAL = No
    -> TINGenerator [BREAKLINES]
TINGenerator
    TOLERANCE = 200
    GROUP_BY = _uuid
    TIN_SURFACE -> Junction_7
Note: AttributeCreator_3 : Input
Junction_7
    -> Junction_8

Bookmark: attributes setter
Note: TINGenerator : TINSurface
Junction_8
    -> AttributeCreator_3
Note: Junction_9 : Output
Junction_11
    -> AttributeCreator_3
Note: TINGenerator_2 : TINSurface
Junction_6
    -> AttributeCreator_3
Note: SolidBuilder : Solid
Junction_2
    -> AttributeCreator_3
Note: Junction : Output
Junction_4
    -> AttributeCreator_3
AttributeCreator_3
    ATTR_TABLE:
      SET_TO citygml_lod_name = lod2MultiSurface
      SET_TO citygml_feature_role = boundedBy
      SET_TO gml_parent_id = FME_CONDITIONAL:DEFAULT_VALUE'_FME_NO_OP_'BOOL_OP;OR;COMPOSITE_TEST;<Unused>;TEST @Value(_uuid) = @Value(id)'@Value(_uuid)'FME_NUM_CONDITIONS2___
      SET_TO name = @Value(name)
    -> GeometryPropertySetter_2
GeometryPropertySetter_2
    SETTYPE_PARAM = Traits From Attributes
    REMOVE_ATTRIBUTE = No
    OVERWRITE_CHOICE = Yes
    SRC_ATTRS = citygml_lod_name
    SET -> RoofSurface (writer CITYGML_1)
RoofSurface (writer CITYGML_1)
    attributes: citygml_feature_role xml_char(200)

Bookmark: Mansard Roof
Note: AttributeFilter : mansard
Junction_19
    -> 3DForcer_9
3DForcer_9
    ZVALATTR = @Value(height)
    KEEPZVAL = No
    -> FaceReplacer_2
    -> Chopper_5
    -> Chopper_3
FaceReplacer_2
    THICKNESS_TOLERANCE = 0.0
    ANGULAR_TOLERANCE = 0.0
    THICKNESS_TOLERANCE_CHOICE = Automatic
    ANGULAR_TOLERANCE_CHOICE = Automatic
    -> Orientor
Orientor
    FLIP_APPEARANCES_CHOICE = Yes
    KIND = REVERSE
    ORIENTED -> SolidBuilder
Chopper_5
    REMNANT_ATTR = _remnant
    MAX_VERTICES = 2
    MODE = By Vertex
    CHOPPED_ATTR = _chopped
    -> AreaBuilder
Chopper_3
    REMNANT_ATTR = _remnant
    MAX_VERTICES = 1
    MODE = By Vertex
    CHOPPED_ATTR = _chopped
    -> Sampler
Sampler
    RATE = 4
    SAMPLE_MODE = No
    SAMPLE_TYPE_LONG = First N Features
    SAMPLED -> NeighborFinder [BASE]
Note: AttributeFilter_2 : mansard
Junction_33
    -> 3DForcer_7
3DForcer_7
    ZVALATTR = @Value(roof_h)
    KEEPZVAL = No
    -> Chopper_4
    -> Chopper_6
Chopper_4
    REMNANT_ATTR = _remnant
    MAX_VERTICES = 1
    MODE = By Vertex
    CHOPPED_ATTR = _chopped
    -> Sampler_2
Sampler_2
    RATE = 4
    SAMPLE_MODE = No
    SAMPLE_TYPE_LONG = First N Features
    SAMPLED -> CoordinateExtractor
CoordinateExtractor
    Y_ATTR = _y
    IND = 0
    Z_ATTR = _z
    MODE = Specify Coordinate
    X_ATTR = _x
    -> NeighborFinder [CANDIDATE]
NeighborFinder
    TREAT_POLYGON_AS = Lines
    CANDIDATES_FIRST = No
    INSERT_VERTEX = No
    ATTR_ACCUM_MODE = Merge Candidate
    MODE = Bases and Candidates
    K = 2
    ATTR_CONFLICT_RES = Use Base
    MATCHED -> VertexCreator
VertexCreator
    ZVAL = @Value(_z)
    MODE_NAME = Add Point
    XVAL = @Value(_x)
    YVAL = @Value(_y)
    -> AreaBuilder
Chopper_6
    REMNANT_ATTR = _remnant
    MAX_VERTICES = 2
    MODE = By Vertex
    CHOPPED_ATTR = _chopped
    -> AreaBuilder
AreaBuilder
    SNAPTYPE_PARAM = None
    ALLOW_CYCLES = No
    CONSIDER_NODE_ELEVATION = no
    POLY_ACCUM_ATTRS_NAME = Get Attributes From One Representative Feature
    CHECK_CURVE_DIRECTION = No
    CONNECT_Z_MODE = First Wins
    DONUT_CREATION = YES
    DROP_HOLES = No
    LINES_AS_SEGMENTS = No
    AREA -> FaceReplacer_3
Note: two of these are facing inwards,instead of outwards, need to isolate and reorient
FaceReplacer_3
    THICKNESS_TOLERANCE_CHOICE = Ignore
    ANGULAR_TOLERANCE_CHOICE = Ignore
    -> SolidBuilder
SolidBuilder
    HOLE_ATTR = _is_void
    DROP_HOLES = No
    SOLID -> Junction
Note: AttributeCreator_3 : Input
Junction
    -> Junction_2

Bookmark: ArchRoof
Note: AttributeFilter : arch
Junction_13
    -> 3DForcer_11
3DForcer_11
    ZVALATTR = @Value(height)
    KEEPZVAL = No
    -> Junction_3
roofEdge_arch_48N (reader ESRISHAPE_9)
    attributes: OBJECTID long, Id long, height double, Shape_Leng double
    -> 3DForcer
    -> 3DForcer_12
3DForcer
    ZVALATTR = @Value(height)
    KEEPZVAL = No
    -> TINGenerator_3 [POINTS/LINES]
TINGenerator_3
    TOLERANCE = 0
    GROUP_BY = Id
    TIN_SURFACE -> Junction_3
3DForcer_12
    ZVALATTR = 30
    KEEPZVAL = No
    -> SnipLastPoint_2
    -> SnipFirstPoint_2
SnipLastPoint_2: Snipper
    ENDVERTEXATTR = -1
    SNIPMODE = Vertex
    STARTVERTEXATTR = -1
    -> Extruder_3
Extruder_3
    DISTANCE = @Value(height)-30
    DIRECTION = Auto
    -> TINGenerator_4 [POINTS/LINES]
TINGenerator_4
    TOLERANCE = 0
    GROUP_BY = Id
    TIN_SURFACE -> Junction_3
SnipFirstPoint_2: Snipper
    ENDVERTEXATTR = 0
    SNIPMODE = Vertex
    STARTVERTEXATTR = 0
    -> Extruder_4
Extruder_4
    DISTANCE = @Value(height)-30
    DIRECTION = Auto
    -> TINGenerator_5 [POINTS/LINES]
TINGenerator_5
    TOLERANCE = 0
    GROUP_BY = Id
    TIN_SURFACE -> Junction_3
Note: Junction_2 : Input
Junction_3
    -> Junction_4
roofEdge_arch_Project (reader ESRISHAPE_3)
    attributes: OBJECTID long, Id long, height double, Shape_Leng double
roofEdge_arch (reader ESRISHAPE_7)
    attributes: Id long, height double

Bookmark: Falt Roof
Note: AttributeFilter_2 : flat
Junction_25
    -> 3DForcer_5
3DForcer_5
    ZVALATTR = @Value(wall_h)
    KEEPZVAL = No
    -> Chopper_2
Chopper_2
    REMNANT_ATTR = _remnant
    MAX_VERTICES = 2
    MODE = By Vertex
    CHOPPED_ATTR = _chopped
    -> Extruder_2
Extruder_2
    DISTANCE = @Value(roof_h)-@Value(wall_h)
    DIRECTION = Vertical
    -> Orientor_5
Note: AttributeFilter_2 : flat
Junction_27
    -> 3DForcer_6
3DForcer_6
    ZVALATTR = @Value(roof_h)
    KEEPZVAL = No
    -> Orientor_5
Orientor_5
    FLIP_APPEARANCES_CHOICE = Yes
    KIND = REVERSE
    ORIENTED -> Junction_9
Junction_9
    -> Junction_10
Note: AttributeCreator_3 : Input
Junction_10
    -> Junction_11

Bookmark: Flat-Hipped Roof Mix
Note: AttributeFilter_2 : flat-hip
Junction_29
    -> GeometryCoercer_2
GeometryCoercer_2
    KIND = fme_line
    GQUERY:
      for $geom in //geometry
      where $geom/count(parent::geometry) = 0
      return number($geom/@fme_id)
    COERCED -> 3DForcer_10
3DForcer_10
    ZVALATTR = @Value(wall_h)
    KEEPZVAL = No
    -> TINGenerator_2 [POINTS/LINES]
Note: AttributeFilter_2 : flat-hip
Junction_31
    -> CenterLineReplacer_2
CenterLineReplacer_2
    MODE = Medial Axis
    CENTERLINE -> 3DForcer_8
3DForcer_8
    ZVALATTR = @Value(roof_h)
    KEEPZVAL = No
    -> TINGenerator_2 [BREAKLINES]
TINGenerator_2
    TOLERANCE = 200
    GROUP_BY = name
    TIN_SURFACE -> Junction_5
Note: AttributeCreator_3 : Input
Junction_5
    -> Junction_6
