FME workspace aq_height_to_3d.fmw

Parameters:
- DestDataset_CESIUM3DTILES = I:\My Drive\3D-Caugiay\3dmodel\3dtile   # Destination Cesium 3D Tiles Folder
- DestDataset_COLLADA = I:\My Drive\3D-Caugiay\3dmodel\dae   # Destination COLLADA Folder
- SourceDataset_ESRISHAPE = ""I:\My Drive\3D-Caugiay\roi\new\corrected_shp_reproject\combined_reproject.shp" "I:\My Drive\3D-Caugiay\roi\new\corrected_shp_reproject\high_building_reprj.shp""   # Source Esri Shapefile(s)
- SourceDataset_ESRISHAPE_3 = I:\My Drive\3D-Caugiay\roi\new\corrected_shp_reproject\combined_reproject2.shp   # Source Esri Shapefile(s)

Readers:
- ESRISHAPE_1: ESRISHAPE from $(SourceDataset_ESRISHAPE)
- ESRISHAPE_2: ESRISHAPE from $(SourceDataset_ESRISHAPE_3)

Writers:
- CESIUM3DTILES_1: CESIUM3DTILES to $(DestDataset_CESIUM3DTILES)
- COLLADA_1: COLLADA to $(DestDataset_COLLADA)

high_building_reprj (reader ESRISHAPE_1)
    attributes: OBJECTID long, Name char(80), height double, aq double, Shape_Leng double, Shape_Area double
combined_reproject2 (reader ESRISHAPE_2)
    attributes: OBJECTID_1 number(18,0), OBJECTID number(18,0), height double, Shape_Leng double, Shape_Le_1 double, Shape_Area double, color double
    -> 3DForcer_2
    -> 3DForcer_3
    -> 3DForcer_4
ColorFilter: AttributeFilter
    ATTR_NAME = color
    ATTR_VALUES = <Empty>,<Missing>,<Null>,<Unfiltered>,1,2,3,4,5,6,7,8
    1 -> color1 [GEOMETRY]
    2 -> color2 [GEOMETRY]
    3 -> color3 [GEOMETRY]
    4 -> color4 [GEOMETRY]
    5 -> color5 [GEOMETRY]
    6 -> color6 [GEOMETRY]
    7 -> color7 [GEOMETRY]
    8 -> color8 [GEOMETRY]
Junction_2
    -> combined_reproject (writer CESIUM3DTILES_1)
    -> combined_reproject (writer COLLADA_1)
combined_reproject (writer COLLADA_1)
combined_reproject (writer CESIUM3DTILES_1)
    attributes: OBJECTID_1 int, OBJECTID int, height float, aq float, Shape_Leng float, Shape_Le_1 float, Shape_Area float

Bookmark: New Bookmark
3DForcer_2
    KEEPZVAL = No
    ZVALATTR = 0
    -> ExtruderHighBlgdL1
ExtruderHighBlgdL1
    DIRECTION = Auto
    DISTANCE = FME_CONDITIONAL:DEFAULT_VALUE'@Value(height)'BOOL_OP;OR;COMPOSITE_TEST;1;TEST @Value(height) > 57'57'FME_NUM_CONDITIONS2___
    EXTRUDED -> ColorFilter

Bookmark: New Bookmark
3DForcer_3
    KEEPZVAL = No
    ZVALATTR = FME_CONDITIONAL:DEFAULT_VALUE'0'BOOL_OP;OR;COMPOSITE_TEST;1;TEST @Value(height) > 57'57'FME_NUM_CONDITIONS2___
    -> ExtruderHighBlgdL2
ExtruderHighBlgdL2
    DIRECTION = Auto
    DISTANCE = FME_CONDITIONAL:DEFAULT_VALUE'@Value(height)-57'BOOL_OP;OR;COMPOSITE_TEST;1;TEST @Value(height) > 138'81'FME_NUM_CONDITIONS2___
    EXTRUDED -> ColorFilter

Bookmark: New Bookmark
3DForcer_4
    KEEPZVAL = No
    ZVALATTR = FME_CONDITIONAL:DEFAULT_VALUE'0'BOOL_OP;OR;COMPOSITE_TEST;1;TEST @Value(height) > 138'138'FME_NUM_CONDITIONS2___
    -> ExtruderHighBlgdL3
ExtruderHighBlgdL3
    DIRECTION = Auto
    DISTANCE = FME_CONDITIONAL:DEFAULT_VALUE'0'BOOL_OP;OR;COMPOSITE_TEST;1;TEST @Value(height) > 138'@Value(height)-138'FME_NUM_CONDITIONS2___
    EXTRUDED -> ColorFilter

Bookmark: Color settings
color1: AppearanceSetter
    ALPHA = 1
    DEF_STORAGE = Create New Definitions
    DIFFUSE_COLOR = 0.666667,1,1
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color2: AppearanceSetter
    ALPHA = 1
    DEF_STORAGE = Create New Definitions
    DIFFUSE_COLOR = 0.333333,0.666667,1
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color3: AppearanceSetter
    ALPHA = 1
    DEF_STORAGE = Create New Definitions
    DIFFUSE_COLOR = 0,1,0.498039
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color4: AppearanceSetter
    ALPHA = 1
    DEF_STORAGE = Create New Definitions
    DIFFUSE_COLOR = 0.333333,0.666667,0
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color5: AppearanceSetter
    ALPHA = 1
    DEF_STORAGE = Create New Definitions
    DIFFUSE_COLOR = 1,1,0
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color6: AppearanceSetter
    ALPHA = 1
    DEF_STORAGE = Create New Definitions
    DIFFUSE_COLOR = 1,0.666667,0
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color7: AppearanceSetter
    ALPHA = 1
    DEF_STORAGE = Create New Definitions
    DIFFUSE_COLOR = 1,0.333333,1
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2
color8: AppearanceSetter
    ALPHA = 1
    DEF_STORAGE = Create New Definitions
    DIFFUSE_COLOR = 1,0,0
    GQUERY:
      for $geom in //geometry
      where $geom/count(parent::geometry) = 0
      return number($geom/@fme_id)
    SET_ON_SIDE = Front and Back Sides
    SHININESS = 0
    SPECULAR_COLOR = 0,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Junction_2

Bookmark: New Bookmark
3DForcer
    KEEPZVAL = No
    ZVALATTR = 0
    -> ExtruderLowBuilding
ExtruderLowBuilding
    DIRECTION = Auto
    DISTANCE = @Value(height)
